############################################################################
#*   Copyright (c) 2014                                                    *  
#*   Jonathan Wiedemann <wood.galaxy@gmail.com>                            *  
#*                                                                         *
#*   This program is free software; you can redistribute it and/or modify  *
#*   it under the terms of the GNU Lesser General Public License (LGPL)    *
#*   as published by the Free Software Foundation; either version 2 of     *
#*   the License, or (at your option) any later version.                   *
#*   for detail see the LICENCE text file.                                 *
#*                                                                         *
#*   This program is distributed in the hope that it will be useful,       *
#*   but WITHOUT ANY WARRANTY; without even the implied warranty of        *
#*   MERCHANTABILITY or FITNESS FOR A PARTICULAR PURPOSE.  See the         *
#*   GNU Library General Public License for more details.                  *
#*                                                                         *
#*   You should have received a copy of the GNU Library General Public     *
#*   License along with this program; if not, write to the Free Software   *
#*   Foundation, Inc., 59 Temple Place, Suite 330, Boston, MA  02111-1307  *
#*   USA                                                                   *
#*                                                                         *
#***************************************************************************

# Ce script transforme tous les maillage en forme, les affines
# Et les exporte au format STEP
# Veuillez modifier le chemin du repertoire, LIGNE 52, dans lequel les fichiers doivent etre exporte
# Par exemple "/home/yoyo/Documents/FreeCAD/Forum/RapMan/" si vous etes sur linux

import FreeCAD
import Part

doc = FreeCAD.ActiveDocument
gui = FreeCADGui.ActiveDocument
for obj in doc.Objects:
	name = obj.Name
	partname = str(name)+str("_part")
	refinename = str(partname)+str("_refine")
	exportname = str(name) + str(".stp")

	doc.addObject("Part::Feature",partname)
	__shape__=Part.Shape()
	__shape__.makeShapeFromMesh(doc.getObject(name).Mesh.Topology,0.100000)
	doc.getObject(partname).Shape=__shape__
	doc.getObject(partname).purgeTouched()
	del __shape__

	App.ActiveDocument.addObject('Part::Feature',refinename).Shape=doc.getObject(partname).Shape.removeSplitter()
	gui.getObject(partname).hide()

	App.ActiveDocument.recompute()
	__objs__=[]
	__objs__.append(doc.getObject(refinename))
	Part.export(__objs__,u"/chemin/vers/repertoire/"+str(exportname))
	del __objs__
